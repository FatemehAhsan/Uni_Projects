# requirements

## 1: horizontal to destination and not accident (Functional)
we move horizontal and want to avoid accident in this move

## 2: move vertical to destination and not accident (Functional)
we want to move vertical and avoid accident

## 3: move horizontal to arrive destination (Functional)
we will move horizontal to arrive destination

## 4: finish horizontal move (Functional)
we arrived horizontal move and want to start vertical move to arrive x and y of destination

## 5: move vertical to arrive vertical destination (Functional)
we want to move vertical to arrive destination

## 6: finish vertical moves (Functional)
we arrived vertical destination and want to arrive to horizontal destination

## 7: arrive destination (Functional)
we arrive our destination and finish movement

## 8: finish vertical not arrive destination (Functional)
we finish vertical move not arrive destination and we add one vertical move

## 9: finish horizontal not arrive destination (Functional)
we finish horizontal move not arrive destination and we add one horizontal move
